--
-- ASN.1 module derived by rob@sectigo.com from EV Guidelines Appendix F,
-- Appendix G, and section 9.8.2.
--

CABForumEVGuidelines DEFINITIONS ::=

BEGIN

-- EXPORTS ALL --

IMPORTS

  -- from the X.500 series
  ub-locality-name, ub-state-name
    FROM UpperBounds {joint-iso-itu-t ds(5) module(1) upperBounds(10) 7}

  -- from Rec. ITU-T X.520 | ISO/IEC 9594-6
  DirectoryString{}, CountryName
    FROM SelectedAttributeTypes {joint-iso-itu-t ds(5) module(1) selectedAttributeTypes(5) 4}

  AlgorithmIdentifier
    FROM PKIX1Explicit88 {iso(1) identified-organization(3) dod(6)
       internet(1) security(5) mechanisms(5) pkix(7) id-mod(0)
       id-pkix1-explicit(18)};


id-evat-jurisdiction OBJECT IDENTIFIER ::= {1 3 6 1 4 1 311 ev(60) 2 1}

id-evat-jurisdiction-localityName OBJECT IDENTIFIER ::= {id-evat-jurisdiction 1}

id-evat-jurisdiction-stateOrProvinceName OBJECT IDENTIFIER ::= {id-evat-jurisdiction 2}

id-evat-jurisdiction-countryName OBJECT IDENTIFIER ::= {id-evat-jurisdiction 3}

jurisdictionLocalityName ATTRIBUTE ::= {
  SUBTYPE OF               name
  WITH SYNTAX              DirectoryString{ub-locality-name}
  LDAP-SYNTAX              directoryString.&id
  LDAP-NAME                {"jurisdictionL"}
  ID                       id-evat-jurisdiction-localityName
}

jurisdictionStateOrProvinceName ATTRIBUTE ::= {
  SUBTYPE OF               name
  WITH SYNTAX              DirectoryString{ub-state-name}
  LDAP-SYNTAX              directoryString.&id
  LDAP-NAME                {"jurisdictionST"}
  ID                       id-evat-jurisdiction-stateOrProvinceName
}

jurisdictionCountryName ATTRIBUTE ::= {
  SUBTYPE OF               name
  WITH SYNTAX              CountryName
  SINGLE VALUE             TRUE
  LDAP-SYNTAX              countryString.&id
  LDAP-NAME                {"jurisdictionC"}
  ID                       id-evat-jurisdiction-countryName
}


cabf OBJECT IDENTIFIER ::= { joint‐iso‐itu‐t(2) international‐organizations(23) ca‐browser‐forum(140) }


cabf-caSigningNonce OBJECT IDENTIFIER ::= { cabf 41 }

caSigningNonce ATTRIBUTE ::= {
  WITH SYNTAX              OCTET STRING
  EQUALITY MATCHING RULE   octetStringMatch
  SINGLE VALUE             TRUE
  ID                       cabf-caSigningNonce
}

cabf-applicantSigningNonce OBJECT IDENTIFIER ::= { cabf 42 }

applicantSigningNonce ATTRIBUTE ::= {
  WITH SYNTAX              OCTET STRING
  EQUALITY MATCHING RULE   octetStringMatch
  SINGLE VALUE             TRUE
  ID                       cabf-applicantSigningNonce
}


cabf-TorServiceDescriptor OBJECT IDENTIFIER ::= { cabf 1 31 }

TorServiceDescriptorHash ::= SEQUENCE {
  onionURI                 UTF8String,
  algorithm                AlgorithmIdentifier,
  subjectPublicKeyHash     BIT STRING
}

TorServiceDescriptorSyntax ::= SEQUENCE SIZE (1..MAX) OF TorServiceDescriptorHash

ext-TorServiceDescriptorHash EXTENSION ::= {
  SYNTAX                   TorServiceDescriptorSyntax
  IDENTIFIED BY            cabf-TorServiceDescriptor
}


id-CABFOrganizationIdentifier OBJECT IDENTIFIER ::= { cabf 3 1 }

CABFOrganizationIdentifier ::= SEQUENCE {
  registrationSchemeIdentifier  PrintableString (SIZE(3)),
  registrationCountry           PrintableString (SIZE(2)),
  registrationStateOrProvince   [0] IMPLICIT PrintableString (SIZE(0..128)) OPTIONAL,
  registrationReference         UTF8String
}

ext-CABFOrganizationIdentifier EXTENSION ::= {
  SYNTAX                   CABFOrganizationIdentifier
  IDENTIFIED BY            id-CABFOrganizationIdentifier
}


END
